'This version of iLogic code by @ClintBrown3D, Adpated from the Inventor API samples
'Originally Published at https://clintbrown.co.uk/setting-dimension-precision-with-ilogic

'Set up Array and Selection for Decimal Places
Dim CB As New ArrayList
CB.Add("Zero")
CB.Add("One")
CB.Add("Two")
CB.Add("Three")
CB.Add("Four")

XX = InputListBox("Set Precision for all Dimensions", CB, CB, Title := "Unofficial Inventor", ListName := "Choose a Precision for all Dimensions")
If XX = "Zero" Then : XX1 = 41729 : XX2 = 42241 : End If
If XX = "One" Then : XX1 = 41730 : XX2 = 42242 : End If
If XX = "Two" Then : XX1 = 41731 : XX2 = 42243 : End If
If XX = "Three" Then : XX1 = 41732 : XX2 = 42244 : End If
If XX = "Four" Then : XX1 = 41733 : XX2 = 42245 : End If
If XX = "" Then : Return : End If

' a reference to the drawing document.
' This assumes a drawing document is active.
Dim oDrawDoc As DrawingDocument
oDrawDoc = ThisApplication.ActiveDocument

'a reference to the active sheet.
Dim oSheet As Sheet
oSheet = oDrawDoc.ActiveSheet

Dim counter As Long
counter = 1

Dim oDrawingDim As DrawingDimension
For Each oDrawingDim In oSheet.DrawingDimensions
	counter = counter + 1
Next

' a reference to the first general dimension in the collection.
Dim oGeneralDim As GeneralDimension
oGeneralDim = oSheet.DrawingDimensions.GeneralDimensions.Item(1)

' a reference to the dimension style of that dimension.
Dim oDimStyle As DimensionStyle
oDimStyle = oGeneralDim.Style

' Modify some properties of the dimension style.
' This will modify all dimensions that use this style.
oDimStyle.LinearPrecision = XX1
oDimStyle.AngularPrecision = XX2
