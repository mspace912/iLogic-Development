'iLogic code by Clint Brown @ClintBrown3D
'Originally posted at https://clintbrown.co.uk/Drawing_Notes_iLogic

SetNotePath = "C:\TEMP\Notes.txt"

' This assumes a drawing document is active.
Dim oDrawDoc As DrawingDocument
 oDrawDoc = ThisApplication.ActiveDocument

'  a reference to the active sheet.
Dim oActiveSheet As Sheet
 oActiveSheet = oDrawDoc.ActiveSheet

'  a reference to the GeneralNotes object
Dim oGeneralNotes As GeneralNotes
 oGeneralNotes = oActiveSheet.DrawingNotes.GeneralNotes

Dim oTG As TransientGeometry
 oTG = ThisApplication.TransientGeometry

'----------READ IN DATA From TEXT File --------------------
oRead = System.IO.File.OpenText(SetNotePath)
EntireFile = oRead.ReadToEnd()
oRead.Close()
Dim sText As String	
sText = EntireFile 
'----------READ IN DATA From TEXT File --------------------

Dim oGeneralNote As GeneralNote
'oGeneralNote = oGeneralNotes.AddFitted(oTG.CreatePoint2d(3, 40), sText) 'Top Left
'oGeneralNote = oGeneralNotes.AddFitted(oTG.CreatePoint2d(50, 40), sText) 'Top Right
oGeneralNote = oGeneralNotes.AddFitted(oTG.CreatePoint2d(50, 8), sText) 'Bottom Right
'oGeneralNote = oGeneralNotes.AddFitted(oTG.CreatePoint2d(3, 6), sText) 'Bottom Left
