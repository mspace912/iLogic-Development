Select Case iProperties.Material

Case "ALM-015"
iProperties.Value("Project", "Description")= "ALUM-SQ TUBE-3/4x3/4x.125wallx21ft"
Parameter("MATERIALWID") = 0.75 in
Parameter.UpdateAfterChange = True
Parameter("MATERIALLEN") = 0.75 in
Parameter.UpdateAfterChange = True
Parameter("WALL") = 0.125 in
Parameter.UpdateAfterChange = True
Parameter("RAWLENGTH") = 21 ft
MessageBox.Show("raw material is 21 ft length" , "Note")

Case "ALM-016"
iProperties.Value("Project", "Description")= "ALUM-SQ TUBE-1x1x.125wallx21ft"
Parameter("MATERIALWID") = 1.0 in
Parameter.UpdateAfterChange = True
Parameter("MATERIALLEN") = 1.0 in
Parameter.UpdateAfterChange = True
Parameter("WALL") = 0.125 in
Parameter.UpdateAfterChange = True
Parameter("RAWLENGTH") = 21 ft
MessageBox.Show("raw material is 21 ft length" , "Note")

Case "ALM-017"
iProperties.Value("Project", "Description")= "ALUM-SQ TUBE-1x2x.125wallx21ft"
Parameter("MATERIALWID") = 1.0 in
Parameter.UpdateAfterChange = True
Parameter("MATERIALLEN") = 2.0 in
Parameter.UpdateAfterChange = True
Parameter("WALL") = 0.125 in
Parameter.UpdateAfterChange = True
Parameter("RAWLENGTH") = 21 ft
MessageBox.Show("raw material is 21 ft length" , "Note")

Case "ALM-018"
iProperties.Value("Project", "Description")= "ALUM-SQ TUBE-1-1/2x1-1/2x.125wallx21ft"
Parameter("MATERIALWID") = 1.5 in
Parameter.UpdateAfterChange = True
Parameter("MATERIALLEN") = 1.5 in
Parameter.UpdateAfterChange = True
Parameter("WALL") = 0.125 in
Parameter.UpdateAfterChange = True
Parameter("RAWLENGTH") = 21 ft
MessageBox.Show("raw material is 21 ft length" , "Note")

Case "ALM-019"
iProperties.Value("Project", "Description")= "ALUM-SQ TUBE-2x2x.125wallx21ft"
Parameter("MATERIALWID") = 2.0 in
Parameter.UpdateAfterChange = True
Parameter("MATERIALLEN") = 2.0 in
Parameter.UpdateAfterChange = True
Parameter("WALL") = 0.125 in
Parameter.UpdateAfterChange = True
Parameter("RAWLENGTH") = 21 ft
MessageBox.Show("raw material is 21 ft length" , "Note")

Case "ALM-020"
iProperties.Value("Project", "Description")= "ALUM-SQ TUBE-2x4x.125wallx21ft"
Parameter("MATERIALWID") = 2.0 in
Parameter.UpdateAfterChange = True
Parameter("MATERIALLEN") = 4.0 in
Parameter.UpdateAfterChange = True
Parameter("WALL") = 0.125 in
Parameter.UpdateAfterChange = True
Parameter("RAWLENGTH") = 21 ft
MessageBox.Show("raw material is 21 ft length" , "Note")

Case "ALM-021"
iProperties.Value("Project", "Description")= "ALUM-SQ TUBE-2x5x.125wallx21ft"
Parameter("MATERIALWID") = 2.0 in
Parameter.UpdateAfterChange = True
Parameter("MATERIALLEN") = 5.0 in
Parameter.UpdateAfterChange = True
Parameter("WALL") = 0.125 in
Parameter.UpdateAfterChange = True
Parameter("RAWLENGTH") = 21 ft
MessageBox.Show("raw material is 21 ft length" , "Note")

Case "ALM-022"
iProperties.Value("Project", "Description")= "ALUM-SQ TUBE-1-3/4x1-3/4x1/8x21ft"
Parameter("MATERIALWID") = 1.75 in
Parameter.UpdateAfterChange = True
Parameter("MATERIALLEN") = 1.75 in
Parameter.UpdateAfterChange = True
Parameter("WALL") = 0.125 in
Parameter.UpdateAfterChange = True
Parameter("RAWLENGTH") = 21 ft
MessageBox.Show("raw material is 21 ft length" , "Note")

Case "ALM-049"
iProperties.Value("Project", "Description")= "ALUM-SQ TUBE-4X4X.125WALLX24FT"
Parameter("MATERIALWID") = 4 in
Parameter.UpdateAfterChange = True
Parameter("MATERIALLEN") = 4 in
Parameter.UpdateAfterChange = True
Parameter("WALL") = 0.125 in
Parameter.UpdateAfterChange = True
Parameter("RAWLENGTH") = 24 ft
MessageBox.Show("raw material is 24 ft length" , "Note")

Case "ALM-060"
iProperties.Value("Project", "Description")= "ALUM-SQ TUBE-2.5X2.5X.125WALLX24FT"
Parameter("MATERIALWID") = 2.5 in
Parameter.UpdateAfterChange = True
Parameter("MATERIALLEN") = 2.5 in
Parameter.UpdateAfterChange = True
Parameter("WALL") = 0.125 in
Parameter.UpdateAfterChange = True
Parameter("RAWLENGTH") = 24 ft
MessageBox.Show("raw material is 24 ft length" , "Note")

Case "ALM-061"
iProperties.Value("Project", "Description")= "ALUM-SQ TUBE-1 X 3 X.125 WALL X 21FT"
Parameter("MATERIALWID") = 1.0 in
Parameter.UpdateAfterChange = True
Parameter("MATERIALLEN") = 3.0 in
Parameter.UpdateAfterChange = True
Parameter("WALL") = 0.125 in
Parameter.UpdateAfterChange = True
Parameter("RAWLENGTH") = 21 ft
MessageBox.Show("raw material is 21 ft length" , "Note")

Case "ALM-063"
iProperties.Value("Project", "Description")= "ALUM-SQ TUBE-1 X 4 X.125 WALL X 24FT"
Parameter("MATERIALWID") = 1.0 in
Parameter.UpdateAfterChange = True
Parameter("MATERIALLEN") = 4.0 in
Parameter.UpdateAfterChange = True
Parameter("WALL") = 0.125 in
Parameter.UpdateAfterChange = True
Parameter("RAWLENGTH") = 24 ft
MessageBox.Show("raw material is 24 ft length" , "Note")

Case "ALM-076"
iProperties.Value("Project", "Description")= "ALUM-SQ TUBE-3 X 3 X .125 WALL X 16FT"
Parameter("MATERIALWID") = 3.0 in
Parameter.UpdateAfterChange = True
Parameter("MATERIALLEN") = 3.0 in
Parameter.UpdateAfterChange = True
Parameter("WALL") = 0.125 in
Parameter.UpdateAfterChange = True
Parameter("RAWLENGTH") = 16 ft
MessageBox.Show("raw material is 16 ft length" , "Note")

Case "ALM-094"
iProperties.Value("Project", "Description")= "ALUM-SQ TUBE-4x4x1/2in wall x 10ft"
Parameter("MATERIALWID") = 4.0 in
Parameter.UpdateAfterChange = True
Parameter("MATERIALLEN") = 4.0 in
Parameter.UpdateAfterChange = True
Parameter("WALL") = 0.5 in
Parameter.UpdateAfterChange = True
Parameter("RAWLENGTH") = 10 ft
MessageBox.Show("raw material is 10 ft length" , "Note")

Case "ALM-109"
iProperties.Value("Project", "Description")= "ALUM-SQ TUBE2X2X.125WX12'-SATIN ANOD"
Parameter("MATERIALWID") = 2.0 in
Parameter.UpdateAfterChange = True
Parameter("MATERIALLEN") = 2.0 in
Parameter.UpdateAfterChange = True
Parameter("WALL") = 0.125 in
Parameter.UpdateAfterChange = True
Parameter("RAWLENGTH") = 12 ft
MessageBox.Show("raw material is 12 ft length" , "Note")

Case "ALM-161"
iProperties.Value("Project", "Description")= "ALUM-SQ TUBE-6x6x.125wallx24ft"
Parameter("MATERIALWID") = 6.0 in
Parameter.UpdateAfterChange = True
Parameter("MATERIALLEN") = 6.0 in
Parameter.UpdateAfterChange = True
Parameter("WALL") = 0.125 in
Parameter.UpdateAfterChange = True
Parameter("RAWLENGTH") = 24 ft
MessageBox.Show("raw material is 24 ft length" , "Note")

Case "ALM-168"
iProperties.Value("Project", "Description")= "ALUM-SQ TUBE-1x1x.125wallx12ft-ANODIZED"
Parameter("MATERIALWID") = 1.0 in
Parameter.UpdateAfterChange = True
Parameter("MATERIALLEN") = 1.0 in
Parameter.UpdateAfterChange = True
Parameter("WALL") = 0.125 in
Parameter.UpdateAfterChange = True
Parameter("RAWLENGTH") = 21 ft
MessageBox.Show("raw material is 12 ft length" , "Note")

Case "OCT-005"
iProperties.Value("Project", "Description")= "ALUM-SQ 40mm OCTANORM EXTRUSION"
Parameter("MATERIALWID") = 1.575 in
Parameter.UpdateAfterChange = True
Parameter("MATERIALLEN") = 1.575 in
Parameter.UpdateAfterChange = True
Parameter("WALL") = 0.059 in
Parameter.UpdateAfterChange = True
Parameter("RAWLENGTH") = 16 ft
MessageBox.Show("raw material is 5000mm or about 16 ft length" , "Note")

Case "OCT-026"
iProperties.Value("Project", "Description")= "OCTANORM-BEAM EXTRUSION - 16 X 25 MM"
Parameter("MATERIALWID") = .9843 in
Parameter.UpdateAfterChange = True
Parameter("MATERIALLEN") = .6299 in
Parameter.UpdateAfterChange = True
Parameter("WALL") = 0.081 in
Parameter.UpdateAfterChange = True
Parameter("RAWLENGTH") = 16 ft
MessageBox.Show("raw material is 5000mm or about 16 ft length" , "Note")

Case "STE-001"
iProperties.Value("Project", "Description")= "STEEL-SQ TUBE-1x1x.125wallx24ft-11ga"
Parameter("MATERIALWID") = 1.0 in
Parameter.UpdateAfterChange = True
Parameter("MATERIALLEN") = 1.0 in
Parameter.UpdateAfterChange = True
Parameter("WALL") = 0.125 in
Parameter.UpdateAfterChange = True
Parameter("RAWLENGTH") = 24 ft
MessageBox.Show("raw material is 24 ft length" , "Note")

Case "STE-002"
iProperties.Value("Project", "Description")= "STEEL-SQ TUBE-1x2x24ft-16ga"
Parameter("MATERIALWID") = 1.0 in
Parameter.UpdateAfterChange = True
Parameter("MATERIALLEN") = 2.0 in
Parameter.UpdateAfterChange = True
Parameter("WALL") = 0.0598 in
Parameter.UpdateAfterChange = True
Parameter("RAWLENGTH") = 24 ft
MessageBox.Show("raw material is 24 ft length" , "Note")

Case "STE-003"
iProperties.Value("Project", "Description")= "STEEL-SQ TUBE-2x2x24ft-16ga"
Parameter("MATERIALWID") = 2.0 in
Parameter.UpdateAfterChange = True
Parameter("MATERIALLEN") = 2.0 in
Parameter.UpdateAfterChange = True
Parameter("WALL") = 0.0598 in
Parameter.UpdateAfterChange = True
Parameter("RAWLENGTH") = 24 ft
MessageBox.Show("raw material is 24 ft length" , "Note")

Case "STE-011"
iProperties.Value("Project", "Description")= "STEEL-RECTANGLE TUBE-3X4X3/8WALL"
Parameter("MATERIALWID") = 3.0 in
Parameter.UpdateAfterChange = True
Parameter("MATERIALLEN") = 4.0 in
Parameter.UpdateAfterChange = True
Parameter("WALL") = 0.375 in
Parameter.UpdateAfterChange = True
Parameter("RAWLENGTH") = 20 ft
MessageBox.Show("raw material is 20 ft length" , "Note")

Case "STE-020"
iProperties.Value("Project", "Description")= "STEEL-SQ TUBE-3x3x1/4 WALL-STRUCTURAL"
Parameter("MATERIALWID") = 3.0 in
Parameter.UpdateAfterChange = True
Parameter("MATERIALLEN") = 3.0 in
Parameter.UpdateAfterChange = True
Parameter("WALL") = 0.25 in
Parameter.UpdateAfterChange = True
Parameter("RAWLENGTH") = 20 ft
MessageBox.Show("raw material is 20 ft length" , "Note")

Case Else
iProperties.Value("Project", "Description")="need description"

MessageBox.Show("not rectangular tube material, description not updated" , "Warning")

End Select
