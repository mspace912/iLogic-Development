Parameter("CORNERRADIUS") = 0.01 in
Parameter("LEGRADIUS") = 0.01 in
Parameter.UpdateAfterChange = True
Select Case iProperties.Material

Case "ALM-031"
iProperties.Value("Project", "Description")= "ALUM-U CHANNEL-1-3/4x1-3/4x1/8 wall x16ft"
Parameter.UpdateAfterChange = True
Parameter("FLANGE01") = 1.75 in
Parameter.UpdateAfterChange = True
Parameter("FLANGE02") = 1.75 in
Parameter.UpdateAfterChange = True
Parameter("FLANGE03") = 1.75 in
Parameter.UpdateAfterChange = True
Parameter("THICKNESS") = 0.125 in
Parameter.UpdateAfterChange = True
Parameter ("LEGRADIUS") = .01 in
Parameter.UpdateAfterChange = True
MessageBox.Show("raw material is 16ft length" , "Note")

Case "ALM-042"
iProperties.Value("Project", "Description")= "ALUM-U CHANNEL-ARCH-2x2x1/8 wall x16ft"
Parameter.UpdateAfterChange = True
Parameter("FLANGE01") = 2 in
Parameter.UpdateAfterChange = True
Parameter("FLANGE02") = 2 in
Parameter.UpdateAfterChange = True
Parameter("FLANGE03") = 2 in
Parameter.UpdateAfterChange = True
Parameter("THICKNESS") = 0.125 in
Parameter.UpdateAfterChange = True
MessageBox.Show("raw material is 16ft length" , "Note")

Case "ALM-058"
iProperties.Value("Project", "Description")= "ALUM-U CHANNEL-1x1x1/8 wall x16ft"
Parameter.UpdateAfterChange = True
Parameter("FLANGE01") = 1 in
Parameter.UpdateAfterChange = True
Parameter("FLANGE02") = 1 in
Parameter.UpdateAfterChange = True
Parameter("FLANGE03") = 1 in
Parameter.UpdateAfterChange = True
Parameter("THICKNESS") = 0.125 in
Parameter.UpdateAfterChange = True
Parameter ("LEGRADIUS") = .01 in
Parameter.UpdateAfterChange = True
MessageBox.Show("raw material is 16ft length" , "Note")

Case "ALM-069"
iProperties.Value("Project", "Description")= "ALUM-U CHANNEL-ARCH-ANOD-1x2x1/8 wall x16ft"
Parameter.UpdateAfterChange = True
Parameter("FLANGE01") = 2 in
Parameter.UpdateAfterChange = True
Parameter("FLANGE02") = 1 in
Parameter.UpdateAfterChange = True
Parameter("FLANGE03") = 1 in
Parameter.UpdateAfterChange = True
Parameter("THICKNESS") = 0.125 in
Parameter.UpdateAfterChange = True
MessageBox.Show("raw material is 16ft length" , "Note")

Case "ALM-079"
iProperties.Value("Project", "Description")= "ALUM-U CHANNEL-ANOD-3/8x1/2x1/16 wall"
Parameter.UpdateAfterChange = True
Parameter("FLANGE01") = 0.375 in
Parameter.UpdateAfterChange = True
Parameter("FLANGE02") = 0.5 in
Parameter.UpdateAfterChange = True
Parameter("FLANGE03") = 0.5 in
Parameter.UpdateAfterChange = True
Parameter("THICKNESS") = 0.0625 in
Parameter.UpdateAfterChange = True
Parameter ("LEGRADIUS") = .01 in
Parameter.UpdateAfterChange = True
MessageBox.Show("raw material is 12ft length" , "Note")

Case "ALM-081"
iProperties.Value("Project", "Description")= "ALUM-UCHANNEL-ANOD-.406x.938x1/16 wall"
Parameter.UpdateAfterChange = True
Parameter("FLANGE01") = 0.406 in
Parameter.UpdateAfterChange = True
Parameter("FLANGE02") = 0.938 in
Parameter.UpdateAfterChange = True
Parameter("FLANGE03") = 0.938 in
Parameter.UpdateAfterChange = True
Parameter("THICKNESS") = 0.0625 in
Parameter.UpdateAfterChange = True
Parameter ("LEGRADIUS") = .01 in
Parameter.UpdateAfterChange = True
MessageBox.Show("raw material is 12ft length" , "Note")

Case "ALM-101"
iProperties.Value("Project", "Description")= "ALUM-J CHANNEL-ANOD-7/8x5/16X1/16 wall x8ft"
Parameter.UpdateAfterChange = True
Parameter("FLANGE01") = 0.43 in
Parameter.UpdateAfterChange = True
Parameter("FLANGE02") = 0.3 in
Parameter.UpdateAfterChange = True
Parameter("FLANGE03") = 0.81 in
Parameter.UpdateAfterChange = True
Parameter("THICKNESS") = 0.0625 in
Parameter.UpdateAfterChange = True
MessageBox.Show("raw material is 8ft length" , "Note")

Case "ALM-165"
iProperties.Value("Project", "Description")= "ALUM-U CHANNEL-ANOD-1x1X1/8 wall x12ft"
Parameter.UpdateAfterChange = True
Parameter("FLANGE01") = 1 in
Parameter.UpdateAfterChange = True
Parameter("FLANGE02") = 1 in
Parameter.UpdateAfterChange = True
Parameter("FLANGE03") = 1 in
Parameter.UpdateAfterChange = True
Parameter("THICKNESS") = 0.125 in
Parameter.UpdateAfterChange = True
Parameter ("LEGRADIUS") = .01 in
Parameter.UpdateAfterChange = True
MessageBox.Show("raw material is 12ft length" , "Note")

Case "OCT-032"
iProperties.Value("Project", "Description")= "OCTANORM-U CHANNEL-20mmx15mmx2mm wall x6m"
Parameter.UpdateAfterChange = True
Parameter("FLANGE01") = 20 mm
Parameter.UpdateAfterChange = True
Parameter("FLANGE02") = 15 mm
Parameter.UpdateAfterChange = True
Parameter("FLANGE03") = 15 mm
Parameter.UpdateAfterChange = True
Parameter("THICKNESS") = 2 mm
Parameter.UpdateAfterChange = True
Parameter ("LEGRADIUS") = .075 mm
Parameter.UpdateAfterChange = True
MessageBox.Show("raw material is 6m length" , "Note")

Case "TRIM-003"
iProperties.Value("Project", "Description")= "FLEXIBLE-BLACK-U CHANNEL-1/2x11/16X1/8 wall 125ft ROLL"
Parameter.UpdateAfterChange = True
Parameter("FLANGE01") = 0.6875 in
Parameter.UpdateAfterChange = True
Parameter("FLANGE02") = 0.5 in
Parameter.UpdateAfterChange = True
Parameter("FLANGE03") = 0.5 in
Parameter.UpdateAfterChange = True
Parameter("THICKNESS") = 0.125 in
Parameter.UpdateAfterChange = True
Parameter ("LEGRADIUS") = .01 in
Parameter.UpdateAfterChange = True
MessageBox.Show("raw material is 125ft ROLL" , "Note")

Case Else
iProperties.Value("Project", "Description")="need description"
Parameter.UpdateAfterChange = True
MessageBox.Show("not an extruded u channel, description not updated" , "Warning")
End Select
